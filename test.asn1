ModuleName DEFINITIONS ::=
BEGIN
Form ::= SEQUENCE {
	age	INTEGER,
	men BOOLEAN,
	name OCTET STRING,
	math Scores,
	engligh Scores,
	chinese Scores
}
form Form ::= {
	age		23,
	men		TRUE,
	name	"xty",
	math	66,
	english 43,
	chinese	76
}
Scores ::= INTEGER
END
